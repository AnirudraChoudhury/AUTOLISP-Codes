(DEFUN c:BASPL()
(setq a1 (getint "\nEnter length of the plate: "))
(setq a2 (getint "\nEnter wdth of the plate: "))
(setq p1 (list 0 0))
(setq p2 (list a1 a2))
(command "rectangle" p1 p2)
(setq a3 (getint "\nEnter length side offset for the hole: "))
(setq a4 (getint "\nEnter width side offset for the hole: "))
(setq p3 (list a3 a4 ))
(setq a5 (getint "\nEnter RADIUS of the hole: "))
(setq a5 (getint "\nEnter Thickness of the Plate: "))
(command "circle" p3 a5)
(setq p4 (getpoint "\nLocation of total: "))
(command "text" p4 "" "" a1xa2xa6 "")
)
