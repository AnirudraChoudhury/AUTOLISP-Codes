(defun c:plwb()
(setq a1 (getint "\nEnter length of the plate: "))
(setq a2 (getint "\nEnter wdth of the plate: "))
(setq a3 (getint "\nEnter Thickness of the Plate: "))
	(setq p1 (getpoint "\nLocation of top view "))
	(setq a11 (car p1))
	(setq a21 (+ a1 a11))
	(setq a12 (cadr p1))
	(setq a22 (+ a2 a12))
	(setq p2 (list a21 a22))
	(command "rectangle" p1 p2)
	(setq p3 (getpoint "\nLocation of front view "))
	(setq a31 (car p3))
	(setq a41 (+ a1 a31))
	(setq a32 (cadr p3))
	(setq a42 (+ a3 a32))
	(setq p4 (list a41 a42))
	(command "rectangle" p3 p4)
	(setq p5 (getpoint "\nLocation of side view "))
	(setq a51 (car p5))
	(setq a61 (+ a3 a51))
	(setq a52 (cadr p5))
	(setq a62 (+ a2 a52))
	(setq p6 (list a61 a62))
	(command "rectangle" p5 p6)
(setq k1 (getint "\nEnter height of the text: "))
(setq q1 (getint "\nEnter Quantity of the plate: "))
(setq p7 (getpoint "\nLocation of plate size: "))
(setq b1 (rtos a1 2 0))
(setq s1 (strlen b1))
(setq m1 (substr b1 1 s1))
(setq b2 (rtos a2 2 0))
(setq s2 (strlen b2))
(setq m2 (substr b2 1 s2))
(setq b3 (rtos a3 2 0))
(setq s3 (strlen b3))
(setq m3 (substr b3 1 s3))
(setq r1 (chr 88))
(setq c1 0.00000785)
(setq w1 (* a1 a2 a3 c1 q1))
(setq b4 (rtos w1 2 2))
(setq b5 (rtos q1 2 0))
(setq l1 (strcat "PL. " m3 " THK." r1 m2 r1 m1 " LG."))
(command "text" p7 k1 "" l1 "")
(setq p8 (getpoint "\nLocation of weight: "))
(command "text" p8 "" "" b4 "")
(setq p9 (getpoint "\nLocation of weight: "))
(command "text" p9 "" "" b5 "")
)
