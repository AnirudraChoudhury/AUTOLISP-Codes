(defun c:gpid ()
(setq k 3)
(setq p1 (getpoint "\nDefine Point [ID]: "))
(setq t1 (car p1))
(setq u1 (/ t1 1000))
(setq k1 (rtos u1 2 k))
(setq s1 (strlen k1))
(setq o1 (substr k1 1 1))
(setq m1 (substr k1 2 s1))
(setq t2 (cadr p1))
(setq u2 (/ t2 1000))
(setq k2 (rtos u2 2 k))
(setq s2 (strlen k2))
(setq o2 (substr k2 1 1))
(setq m2 (substr k2 2 s2))
(setq r3 (chr 78))
(setq r4 (chr 61))
(setq r5 (chr 40))
(setq r6 (chr 45))
(setq r7 (chr 41))
(if (= o2 (chr 45))
(setq l1 (strcat r3 r4 r5 r6 r7 m2))
(setq l1 (strcat r3 r4 k2))
)
(setq r1 (chr 69))
(setq r2 (chr 61))
(if (= o1 (chr 45))
(setq l2 (strcat r1 r2 r5 r6 r7 m1))
(setq l2 (strcat r1 r2 k1))
)
(setq p2 (getpoint "\nText Location: "))
(command "QLEADER" p1 p2 "" "" l1 l2 "")
)
